BITSTRINGS DEFINITIONS AUTOMATIC TAGS ::= BEGIN

-- unconstrained
BITSTRING-NULL-NULL-FALSE ::= BIT STRING

-- semi-constrained (lb only)
BITSTRING-0-NULL-FALSE    ::= BIT STRING (SIZE (0..MAX))
BITSTRING-1-NULL-FALSE    ::= BIT STRING (SIZE (1..MAX))
BITSTRING-10-NULL-FALSE   ::= BIT STRING (SIZE (10..MAX))

-- fixed size (lb==ub), not extensible
BITSTRING-1-1-FALSE       ::= BIT STRING (SIZE (1))
BITSTRING-8-8-FALSE       ::= BIT STRING (SIZE (8))
BITSTRING-16-16-FALSE     ::= BIT STRING (SIZE (16))
BITSTRING-32-32-FALSE     ::= BIT STRING (SIZE (32))
BITSTRING-64-64-FALSE     ::= BIT STRING (SIZE (64))
BITSTRING-128-128-FALSE   ::= BIT STRING (SIZE (128))

-- constrained (lb=0, various ub), not extensible
BITSTRING-0-2-FALSE       ::= BIT STRING (SIZE (0..2))
BITSTRING-0-4-FALSE       ::= BIT STRING (SIZE (0..4))
BITSTRING-0-8-FALSE       ::= BIT STRING (SIZE (0..8))
BITSTRING-0-10-FALSE      ::= BIT STRING (SIZE (0..10))
BITSTRING-0-16-FALSE      ::= BIT STRING (SIZE (0..16))
BITSTRING-0-32-FALSE      ::= BIT STRING (SIZE (0..32))
BITSTRING-0-64-FALSE      ::= BIT STRING (SIZE (0..64))
BITSTRING-0-128-FALSE     ::= BIT STRING (SIZE (0..128))
BITSTRING-0-256-FALSE     ::= BIT STRING (SIZE (0..256))
BITSTRING-0-512-FALSE     ::= BIT STRING (SIZE (0..512))
BITSTRING-0-1024-FALSE    ::= BIT STRING (SIZE (0..1024))
BITSTRING-0-2048-FALSE    ::= BIT STRING (SIZE (0..2048))
BITSTRING-0-4096-FALSE    ::= BIT STRING (SIZE (0..4096))
BITSTRING-0-8192-FALSE    ::= BIT STRING (SIZE (0..8192))
BITSTRING-0-16384-FALSE   ::= BIT STRING (SIZE (0..16384))
BITSTRING-0-32768-FALSE   ::= BIT STRING (SIZE (0..32768))
BITSTRING-0-65536-FALSE   ::= BIT STRING (SIZE (0..65536))
BITSTRING-0-131072-FALSE  ::= BIT STRING (SIZE (0..131072))
BITSTRING-0-262144-FALSE  ::= BIT STRING (SIZE (0..262144))
BITSTRING-0-524288-FALSE  ::= BIT STRING (SIZE (0..524288))
BITSTRING-0-1048576-FALSE ::= BIT STRING (SIZE (0..1048576))
BITSTRING-0-2097152-FALSE ::= BIT STRING (SIZE (0..2097152))

-- constrained (lb=0, various ub), extensible
BITSTRING-0-0-TRUE        ::= BIT STRING (SIZE (0, ...))
BITSTRING-0-1-TRUE        ::= BIT STRING (SIZE (0..1, ...))
BITSTRING-0-2-TRUE        ::= BIT STRING (SIZE (0..2, ...))
BITSTRING-0-4-TRUE        ::= BIT STRING (SIZE (0..4, ...))
BITSTRING-0-8-TRUE        ::= BIT STRING (SIZE (0..8, ...))
BITSTRING-0-16-TRUE       ::= BIT STRING (SIZE (0..16, ...))
BITSTRING-0-32-TRUE       ::= BIT STRING (SIZE (0..32, ...))
BITSTRING-0-64-TRUE       ::= BIT STRING (SIZE (0..64, ...))
BITSTRING-0-128-TRUE      ::= BIT STRING (SIZE (0..128, ...))
BITSTRING-0-256-TRUE      ::= BIT STRING (SIZE (0..256, ...))
BITSTRING-0-512-TRUE      ::= BIT STRING (SIZE (0..512, ...))
BITSTRING-0-1024-TRUE     ::= BIT STRING (SIZE (0..1024, ...))
BITSTRING-0-2048-TRUE     ::= BIT STRING (SIZE (0..2048, ...))
BITSTRING-0-4096-TRUE     ::= BIT STRING (SIZE (0..4096, ...))
BITSTRING-0-8192-TRUE     ::= BIT STRING (SIZE (0..8192, ...))
BITSTRING-0-16384-TRUE    ::= BIT STRING (SIZE (0..16384, ...))
BITSTRING-0-32768-TRUE    ::= BIT STRING (SIZE (0..32768, ...))
BITSTRING-0-65536-TRUE    ::= BIT STRING (SIZE (0..65536, ...))
BITSTRING-0-131072-TRUE   ::= BIT STRING (SIZE (0..131072, ...))
BITSTRING-0-262144-TRUE   ::= BIT STRING (SIZE (0..262144, ...))
BITSTRING-0-524288-TRUE   ::= BIT STRING (SIZE (0..524288, ...))

-- fixed size (lb==ub), extensible
BITSTRING-1-1-TRUE        ::= BIT STRING (SIZE (1, ...))
BITSTRING-8-8-TRUE        ::= BIT STRING (SIZE (8, ...))
BITSTRING-16-16-TRUE      ::= BIT STRING (SIZE (16, ...))
BITSTRING-32-32-TRUE      ::= BIT STRING (SIZE (32, ...))
BITSTRING-64-64-TRUE      ::= BIT STRING (SIZE (64, ...))
BITSTRING-128-128-TRUE    ::= BIT STRING (SIZE (128, ...))

-- lb > 0 constrained, not extensible
BITSTRING-4-16-FALSE      ::= BIT STRING (SIZE (4..16))
BITSTRING-8-32-FALSE      ::= BIT STRING (SIZE (8..32))
BITSTRING-16-64-FALSE     ::= BIT STRING (SIZE (16..64))

-- lb > 0 constrained, extensible
BITSTRING-4-16-TRUE       ::= BIT STRING (SIZE (4..16, ...))
BITSTRING-8-32-TRUE       ::= BIT STRING (SIZE (8..32, ...))
BITSTRING-16-64-TRUE      ::= BIT STRING (SIZE (16..64, ...))

END
