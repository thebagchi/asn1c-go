OCTETSTRINGS DEFINITIONS AUTOMATIC TAGS ::= BEGIN

-- unconstrained
OCTETSTRING-NULL-NULL-FALSE ::= OCTET STRING

-- semi-constrained (lb only)
OCTETSTRING-0-NULL-FALSE    ::= OCTET STRING (SIZE (0..MAX))
OCTETSTRING-1-NULL-FALSE    ::= OCTET STRING (SIZE (1..MAX))
OCTETSTRING-10-NULL-FALSE   ::= OCTET STRING (SIZE (10..MAX))

-- fixed size (lb==ub), not extensible
OCTETSTRING-1-1-FALSE       ::= OCTET STRING (SIZE (1))
OCTETSTRING-4-4-FALSE       ::= OCTET STRING (SIZE (4))
OCTETSTRING-8-8-FALSE       ::= OCTET STRING (SIZE (8))
OCTETSTRING-16-16-FALSE     ::= OCTET STRING (SIZE (16))
OCTETSTRING-64-64-FALSE     ::= OCTET STRING (SIZE (64))

-- boundary ranges (length determinant thresholds), not extensible
OCTETSTRING-1-127-FALSE     ::= OCTET STRING (SIZE (1..127))
OCTETSTRING-1-128-FALSE     ::= OCTET STRING (SIZE (1..128))
OCTETSTRING-1-255-FALSE     ::= OCTET STRING (SIZE (1..255))
OCTETSTRING-1-256-FALSE     ::= OCTET STRING (SIZE (1..256))

-- constrained (lb=0, various ub), not extensible
OCTETSTRING-0-2-FALSE       ::= OCTET STRING (SIZE (0..2))
OCTETSTRING-0-4-FALSE       ::= OCTET STRING (SIZE (0..4))
OCTETSTRING-0-8-FALSE       ::= OCTET STRING (SIZE (0..8))
OCTETSTRING-0-10-FALSE      ::= OCTET STRING (SIZE (0..10))
OCTETSTRING-0-16-FALSE      ::= OCTET STRING (SIZE (0..16))
OCTETSTRING-0-32-FALSE      ::= OCTET STRING (SIZE (0..32))
OCTETSTRING-0-64-FALSE      ::= OCTET STRING (SIZE (0..64))
OCTETSTRING-0-128-FALSE     ::= OCTET STRING (SIZE (0..128))
OCTETSTRING-0-256-FALSE     ::= OCTET STRING (SIZE (0..256))
OCTETSTRING-0-512-FALSE     ::= OCTET STRING (SIZE (0..512))
OCTETSTRING-0-1024-FALSE    ::= OCTET STRING (SIZE (0..1024))
OCTETSTRING-0-2048-FALSE    ::= OCTET STRING (SIZE (0..2048))
OCTETSTRING-0-4096-FALSE    ::= OCTET STRING (SIZE (0..4096))
OCTETSTRING-0-8192-FALSE    ::= OCTET STRING (SIZE (0..8192))
OCTETSTRING-0-16384-FALSE   ::= OCTET STRING (SIZE (0..16384))
OCTETSTRING-0-32768-FALSE   ::= OCTET STRING (SIZE (0..32768))
OCTETSTRING-0-65536-FALSE   ::= OCTET STRING (SIZE (0..65536))
OCTETSTRING-0-131072-FALSE  ::= OCTET STRING (SIZE (0..131072))
OCTETSTRING-0-262144-FALSE  ::= OCTET STRING (SIZE (0..262144))
OCTETSTRING-0-524288-FALSE  ::= OCTET STRING (SIZE (0..524288))
OCTETSTRING-0-1048576-FALSE ::= OCTET STRING (SIZE (0..1048576))
OCTETSTRING-0-2097152-FALSE ::= OCTET STRING (SIZE (0..2097152))

-- constrained (lb=0, various ub), extensible
OCTETSTRING-0-0-TRUE        ::= OCTET STRING (SIZE (0, ...))
OCTETSTRING-0-1-TRUE        ::= OCTET STRING (SIZE (0..1, ...))
OCTETSTRING-0-2-TRUE        ::= OCTET STRING (SIZE (0..2, ...))
OCTETSTRING-0-4-TRUE        ::= OCTET STRING (SIZE (0..4, ...))
OCTETSTRING-0-8-TRUE        ::= OCTET STRING (SIZE (0..8, ...))
OCTETSTRING-0-16-TRUE       ::= OCTET STRING (SIZE (0..16, ...))
OCTETSTRING-0-32-TRUE       ::= OCTET STRING (SIZE (0..32, ...))
OCTETSTRING-0-64-TRUE       ::= OCTET STRING (SIZE (0..64, ...))
OCTETSTRING-0-128-TRUE      ::= OCTET STRING (SIZE (0..128, ...))
OCTETSTRING-0-256-TRUE      ::= OCTET STRING (SIZE (0..256, ...))
OCTETSTRING-0-512-TRUE      ::= OCTET STRING (SIZE (0..512, ...))
OCTETSTRING-0-1024-TRUE     ::= OCTET STRING (SIZE (0..1024, ...))
OCTETSTRING-0-2048-TRUE     ::= OCTET STRING (SIZE (0..2048, ...))
OCTETSTRING-0-4096-TRUE     ::= OCTET STRING (SIZE (0..4096, ...))
OCTETSTRING-0-8192-TRUE     ::= OCTET STRING (SIZE (0..8192, ...))
OCTETSTRING-0-16384-TRUE    ::= OCTET STRING (SIZE (0..16384, ...))
OCTETSTRING-0-32768-TRUE    ::= OCTET STRING (SIZE (0..32768, ...))
OCTETSTRING-0-65536-TRUE    ::= OCTET STRING (SIZE (0..65536, ...))
OCTETSTRING-0-131072-TRUE   ::= OCTET STRING (SIZE (0..131072, ...))
OCTETSTRING-0-262144-TRUE   ::= OCTET STRING (SIZE (0..262144, ...))
OCTETSTRING-0-524288-TRUE   ::= OCTET STRING (SIZE (0..524288, ...))

-- fixed size (lb==ub), extensible
OCTETSTRING-1-1-TRUE        ::= OCTET STRING (SIZE (1, ...))
OCTETSTRING-4-4-TRUE        ::= OCTET STRING (SIZE (4, ...))
OCTETSTRING-8-8-TRUE        ::= OCTET STRING (SIZE (8, ...))
OCTETSTRING-16-16-TRUE      ::= OCTET STRING (SIZE (16, ...))
OCTETSTRING-64-64-TRUE      ::= OCTET STRING (SIZE (64, ...))

-- boundary ranges, extensible
OCTETSTRING-1-127-TRUE      ::= OCTET STRING (SIZE (1..127, ...))
OCTETSTRING-1-128-TRUE      ::= OCTET STRING (SIZE (1..128, ...))
OCTETSTRING-1-255-TRUE      ::= OCTET STRING (SIZE (1..255, ...))
OCTETSTRING-1-256-TRUE      ::= OCTET STRING (SIZE (1..256, ...))

-- lb > 0 constrained, not extensible
OCTETSTRING-4-16-FALSE      ::= OCTET STRING (SIZE (4..16))
OCTETSTRING-8-32-FALSE      ::= OCTET STRING (SIZE (8..32))
OCTETSTRING-16-64-FALSE     ::= OCTET STRING (SIZE (16..64))

-- lb > 0 constrained, extensible
OCTETSTRING-4-16-TRUE       ::= OCTET STRING (SIZE (4..16, ...))
OCTETSTRING-8-32-TRUE       ::= OCTET STRING (SIZE (8..32, ...))
OCTETSTRING-16-64-TRUE      ::= OCTET STRING (SIZE (16..64, ...))

END
