INTEGERS DEFINITIONS AUTOMATIC TAGS ::= BEGIN

-- unconstrained
INTEGER-NULL-NULL-FALSE ::= INTEGER

-- semi-constrained (lower bound only), not extensible
INTEGER-0-NULL-FALSE      ::= INTEGER (0..MAX)
INTEGER-10-NULL-FALSE     ::= INTEGER (10..MAX)
INTEGER-20-NULL-FALSE     ::= INTEGER (20..MAX)
INTEGER-100-NULL-FALSE    ::= INTEGER (100..MAX)
INTEGER-N1-NULL-FALSE     ::= INTEGER (-1..MAX)
INTEGER-N10-NULL-FALSE    ::= INTEGER (-10..MAX)
INTEGER-N100-NULL-FALSE   ::= INTEGER (-100..MAX)
INTEGER-N200-NULL-FALSE   ::= INTEGER (-200..MAX)

-- semi-constrained (lower bound only), extensible
INTEGER-0-NULL-TRUE       ::= INTEGER (0..MAX, ...)
INTEGER-N1-NULL-TRUE      ::= INTEGER (-1..MAX, ...)
INTEGER-10-NULL-TRUE      ::= INTEGER (10..MAX, ...)
INTEGER-20-NULL-TRUE      ::= INTEGER (20..MAX, ...)
INTEGER-N100-NULL-TRUE    ::= INTEGER (-100..MAX, ...)

-- constrained (0 to various upper bounds), not extensible
INTEGER-0-1-FALSE             ::= INTEGER (0..1)
INTEGER-0-2-FALSE             ::= INTEGER (0..2)
INTEGER-0-4-FALSE             ::= INTEGER (0..4)
INTEGER-0-8-FALSE             ::= INTEGER (0..8)
INTEGER-0-16-FALSE            ::= INTEGER (0..16)
INTEGER-0-32-FALSE            ::= INTEGER (0..32)
INTEGER-0-64-FALSE            ::= INTEGER (0..64)
INTEGER-0-99-FALSE            ::= INTEGER (0..99)
INTEGER-0-100-FALSE           ::= INTEGER (0..100)
INTEGER-0-127-FALSE           ::= INTEGER (0..127)
INTEGER-0-128-FALSE           ::= INTEGER (0..128)
INTEGER-0-200-FALSE           ::= INTEGER (0..200)
INTEGER-0-253-FALSE           ::= INTEGER (0..253)
INTEGER-0-254-FALSE           ::= INTEGER (0..254)
INTEGER-0-255-FALSE           ::= INTEGER (0..255)
INTEGER-0-256-FALSE           ::= INTEGER (0..256)
INTEGER-0-257-FALSE           ::= INTEGER (0..257)
INTEGER-0-511-FALSE           ::= INTEGER (0..511)
INTEGER-0-512-FALSE           ::= INTEGER (0..512)
INTEGER-0-1000-FALSE          ::= INTEGER (0..1000)
INTEGER-0-1024-FALSE          ::= INTEGER (0..1024)
INTEGER-0-2047-FALSE          ::= INTEGER (0..2047)
INTEGER-0-2048-FALSE          ::= INTEGER (0..2048)
INTEGER-0-4096-FALSE          ::= INTEGER (0..4096)
INTEGER-0-8192-FALSE          ::= INTEGER (0..8192)
INTEGER-0-10000-FALSE         ::= INTEGER (0..10000)
INTEGER-0-16384-FALSE         ::= INTEGER (0..16384)
INTEGER-0-32000-FALSE         ::= INTEGER (0..32000)
INTEGER-0-32768-FALSE         ::= INTEGER (0..32768)
INTEGER-0-65534-FALSE         ::= INTEGER (0..65534)
INTEGER-0-65535-FALSE         ::= INTEGER (0..65535)
INTEGER-0-65536-FALSE         ::= INTEGER (0..65536)
INTEGER-0-65537-FALSE         ::= INTEGER (0..65537)
INTEGER-0-100000-FALSE        ::= INTEGER (0..100000)
INTEGER-0-131072-FALSE        ::= INTEGER (0..131072)
INTEGER-0-262144-FALSE        ::= INTEGER (0..262144)
INTEGER-0-524288-FALSE        ::= INTEGER (0..524288)
INTEGER-0-1000000-FALSE       ::= INTEGER (0..1000000)
INTEGER-0-1048576-FALSE       ::= INTEGER (0..1048576)
INTEGER-0-2097152-FALSE       ::= INTEGER (0..2097152)
INTEGER-0-4194304-FALSE       ::= INTEGER (0..4194304)
INTEGER-0-8388608-FALSE       ::= INTEGER (0..8388608)
INTEGER-0-16777216-FALSE      ::= INTEGER (0..16777216)
INTEGER-0-33554432-FALSE      ::= INTEGER (0..33554432)
INTEGER-0-67108864-FALSE      ::= INTEGER (0..67108864)
INTEGER-0-134217728-FALSE     ::= INTEGER (0..134217728)
INTEGER-0-268435456-FALSE     ::= INTEGER (0..268435456)
INTEGER-0-536870911-FALSE     ::= INTEGER (0..536870911)
INTEGER-0-1073741823-FALSE    ::= INTEGER (0..1073741823)
INTEGER-0-2147483647-FALSE    ::= INTEGER (0..2147483647)
INTEGER-0-4294967295-FALSE    ::= INTEGER (0..4294967295)

-- other constrained ranges (non-negative), not extensible
INTEGER-10-150-FALSE    ::= INTEGER (10..150)
INTEGER-20-40-FALSE     ::= INTEGER (20..40)
INTEGER-50-100-FALSE    ::= INTEGER (50..100)
INTEGER-50-50-FALSE     ::= INTEGER (50..50)
INTEGER-100-200-FALSE   ::= INTEGER (100..200)
INTEGER-1-1-FALSE       ::= INTEGER (1..1)
INTEGER-1-3-FALSE       ::= INTEGER (1..3)
INTEGER-3-6-FALSE       ::= INTEGER (3..6)
INTEGER-4000-4254-FALSE ::= INTEGER (4000..4254)
INTEGER-4000-4255-FALSE ::= INTEGER (4000..4255)
INTEGER-1-65538-FALSE   ::= INTEGER (1..65538)

-- constrained with negative bounds, not extensible
INTEGER-N200-N10-FALSE  ::= INTEGER (-200..-10)
INTEGER-N100-100-FALSE  ::= INTEGER (-100..100)
INTEGER-N100-N10-FALSE  ::= INTEGER (-100..-10)
INTEGER-N50-50-FALSE    ::= INTEGER (-50..50)
INTEGER-N10-10-FALSE    ::= INTEGER (-10..10)
INTEGER-N128-127-FALSE  ::= INTEGER (-128..127)
INTEGER-N2147483648-2147483647-FALSE ::= INTEGER (-2147483648..2147483647)

-- constrained (0 to various upper bounds), extensible
INTEGER-0-1-TRUE              ::= INTEGER (0..1, ...)
INTEGER-0-2-TRUE              ::= INTEGER (0..2, ...)
INTEGER-0-4-TRUE              ::= INTEGER (0..4, ...)
INTEGER-0-8-TRUE              ::= INTEGER (0..8, ...)
INTEGER-0-16-TRUE             ::= INTEGER (0..16, ...)
INTEGER-0-32-TRUE             ::= INTEGER (0..32, ...)
INTEGER-0-64-TRUE             ::= INTEGER (0..64, ...)
INTEGER-0-99-TRUE             ::= INTEGER (0..99, ...)
INTEGER-0-100-TRUE            ::= INTEGER (0..100, ...)
INTEGER-0-128-TRUE            ::= INTEGER (0..128, ...)
INTEGER-0-200-TRUE            ::= INTEGER (0..200, ...)
INTEGER-0-256-TRUE            ::= INTEGER (0..256, ...)
INTEGER-0-257-TRUE            ::= INTEGER (0..257, ...)
INTEGER-0-512-TRUE            ::= INTEGER (0..512, ...)
INTEGER-0-1000-TRUE           ::= INTEGER (0..1000, ...)
INTEGER-0-1024-TRUE           ::= INTEGER (0..1024, ...)
INTEGER-0-2048-TRUE           ::= INTEGER (0..2048, ...)
INTEGER-0-4096-TRUE           ::= INTEGER (0..4096, ...)
INTEGER-0-8192-TRUE           ::= INTEGER (0..8192, ...)
INTEGER-0-10000-TRUE          ::= INTEGER (0..10000, ...)
INTEGER-0-16384-TRUE          ::= INTEGER (0..16384, ...)
INTEGER-0-32000-TRUE          ::= INTEGER (0..32000, ...)
INTEGER-0-32768-TRUE          ::= INTEGER (0..32768, ...)
INTEGER-0-65535-TRUE          ::= INTEGER (0..65535, ...)
INTEGER-0-65536-TRUE          ::= INTEGER (0..65536, ...)
INTEGER-0-100000-TRUE         ::= INTEGER (0..100000, ...)
INTEGER-0-131072-TRUE         ::= INTEGER (0..131072, ...)
INTEGER-0-262144-TRUE         ::= INTEGER (0..262144, ...)
INTEGER-0-524288-TRUE         ::= INTEGER (0..524288, ...)
INTEGER-0-1000000-TRUE        ::= INTEGER (0..1000000, ...)
INTEGER-0-1048576-TRUE        ::= INTEGER (0..1048576, ...)
INTEGER-0-2097152-TRUE        ::= INTEGER (0..2097152, ...)
INTEGER-0-4194304-TRUE        ::= INTEGER (0..4194304, ...)
INTEGER-0-8388608-TRUE        ::= INTEGER (0..8388608, ...)
INTEGER-0-16777216-TRUE       ::= INTEGER (0..16777216, ...)
INTEGER-0-33554432-TRUE       ::= INTEGER (0..33554432, ...)
INTEGER-0-67108864-TRUE       ::= INTEGER (0..67108864, ...)
INTEGER-0-134217728-TRUE      ::= INTEGER (0..134217728, ...)
INTEGER-0-268435456-TRUE      ::= INTEGER (0..268435456, ...)
INTEGER-0-536870911-TRUE      ::= INTEGER (0..536870911, ...)
INTEGER-0-1073741823-TRUE     ::= INTEGER (0..1073741823, ...)
INTEGER-0-2147483647-TRUE     ::= INTEGER (0..2147483647, ...)
INTEGER-0-4294967295-TRUE     ::= INTEGER (0..4294967295, ...)

-- other constrained ranges, extensible
INTEGER-10-150-TRUE     ::= INTEGER (10..150, ...)
INTEGER-20-40-TRUE      ::= INTEGER (20..40, ...)
INTEGER-50-100-TRUE     ::= INTEGER (50..100, ...)
INTEGER-50-50-TRUE      ::= INTEGER (50..50, ...)
INTEGER-100-100-TRUE    ::= INTEGER (100..100, ...)
INTEGER-100-200-TRUE    ::= INTEGER (100..200, ...)
INTEGER-1000-1000-TRUE  ::= INTEGER (1000..1000, ...)
INTEGER-1-1-TRUE        ::= INTEGER (1..1, ...)
INTEGER-1-3-TRUE        ::= INTEGER (1..3, ...)
INTEGER-3-6-TRUE        ::= INTEGER (3..6, ...)
INTEGER-4000-4254-TRUE  ::= INTEGER (4000..4254, ...)
INTEGER-4000-4255-TRUE  ::= INTEGER (4000..4255, ...)
INTEGER-1-65538-TRUE    ::= INTEGER (1..65538, ...)

-- constrained with negative bounds, extensible
INTEGER-N500-500-TRUE   ::= INTEGER (-500..500, ...)
INTEGER-N200-N10-TRUE   ::= INTEGER (-200..-10, ...)
INTEGER-N100-100-TRUE   ::= INTEGER (-100..100, ...)
INTEGER-N100-N10-TRUE   ::= INTEGER (-100..-10, ...)
INTEGER-N50-50-TRUE     ::= INTEGER (-50..50, ...)
INTEGER-N10-10-TRUE     ::= INTEGER (-10..10, ...)
INTEGER-N128-127-TRUE   ::= INTEGER (-128..127, ...)
INTEGER-N2147483648-2147483647-TRUE ::= INTEGER (-2147483648..2147483647, ...)

END
