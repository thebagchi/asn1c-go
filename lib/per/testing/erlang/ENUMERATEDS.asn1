ENUMERATEDS DEFINITIONS AUTOMATIC TAGS ::= BEGIN

ENUM-2-0-FALSE ::= ENUMERATED {
    m-1,
    m-2
}

ENUM-3-0-FALSE ::= ENUMERATED {
    m-1,
    m-2,
    m-3
}

ENUM-4-0-FALSE ::= ENUMERATED {
    m-1,
    m-2,
    m-3,
    m-4
}

ENUM-5-0-FALSE ::= ENUMERATED {
    m-1,
    m-2,
    m-3,
    m-4,
    m-5
}

ENUM-6-0-FALSE ::= ENUMERATED {
    m-1,
    m-2,
    m-3,
    m-4,
    m-5,
    m-6
}

ENUM-7-0-FALSE ::= ENUMERATED {
    m-1,
    m-2,
    m-3,
    m-4,
    m-5,
    m-6,
    m-7
}

ENUM-8-0-FALSE ::= ENUMERATED {
    m-1,
    m-2,
    m-3,
    m-4,
    m-5,
    m-6,
    m-7,
    m-8
}

ENUM-9-0-FALSE ::= ENUMERATED {
    m-1,
    m-2,
    m-3,
    m-4,
    m-5,
    m-6,
    m-7,
    m-8,
    m-9
}

ENUM-10-0-FALSE ::= ENUMERATED {
    m-1,
    m-2,
    m-3,
    m-4,
    m-5,
    m-6,
    m-7,
    m-8,
    m-9,
    m-10
}

ENUM-15-0-FALSE ::= ENUMERATED {
    m-1,
    m-2,
    m-3,
    m-4,
    m-5,
    m-6,
    m-7,
    m-8,
    m-9,
    m-10,
    m-11,
    m-12,
    m-13,
    m-14,
    m-15
}

ENUM-16-0-FALSE ::= ENUMERATED {
    m-1,
    m-2,
    m-3,
    m-4,
    m-5,
    m-6,
    m-7,
    m-8,
    m-9,
    m-10,
    m-11,
    m-12,
    m-13,
    m-14,
    m-15,
    m-16
}

ENUM-17-0-FALSE ::= ENUMERATED {
    m-1,
    m-2,
    m-3,
    m-4,
    m-5,
    m-6,
    m-7,
    m-8,
    m-9,
    m-10,
    m-11,
    m-12,
    m-13,
    m-14,
    m-15,
    m-16,
    m-17
}

ENUM-33-0-FALSE ::= ENUMERATED {
    m-1,
    m-2,
    m-3,
    m-4,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33
}

ENUM-65-0-FALSE ::= ENUMERATED {
    m-1,
    m-2,
    m-3,
    m-4,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33,
    m-34,
    m-35,
    m-36,
    m-37,
    m-38,
    m-39,
    m-40,
    m-41,
    m-42,
    m-43,
    m-44,
    m-45,
    m-46,
    m-47,
    m-48,
    m-49,
    m-50,
    m-51,
    m-52,
    m-53,
    m-54,
    m-55,
    m-56,
    m-57,
    m-58,
    m-59,
    m-60,
    m-61,
    m-62,
    m-63,
    m-64,
    m-65
}

ENUM-128-0-FALSE ::= ENUMERATED {
    m-1,
    m-2,
    m-3,
    m-4,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33,
    m-34,
    m-35,
    m-36,
    m-37,
    m-38,
    m-39,
    m-40,
    m-41,
    m-42,
    m-43,
    m-44,
    m-45,
    m-46,
    m-47,
    m-48,
    m-49,
    m-50,
    m-51,
    m-52,
    m-53,
    m-54,
    m-55,
    m-56,
    m-57,
    m-58,
    m-59,
    m-60,
    m-61,
    m-62,
    m-63,
    m-64,
    m-65,
    m-66,
    m-67,
    m-68,
    m-69,
    m-70,
    m-71,
    m-72,
    m-73,
    m-74,
    m-75,
    m-76,
    m-77,
    m-78,
    m-79,
    m-80,
    m-81,
    m-82,
    m-83,
    m-84,
    m-85,
    m-86,
    m-87,
    m-88,
    m-89,
    m-90,
    m-91,
    m-92,
    m-93,
    m-94,
    m-95,
    m-96,
    m-97,
    m-98,
    m-99,
    m-100,
    m-101,
    m-102,
    m-103,
    m-104,
    m-105,
    m-106,
    m-107,
    m-108,
    m-109,
    m-110,
    m-111,
    m-112,
    m-113,
    m-114,
    m-115,
    m-116,
    m-117,
    m-118,
    m-119,
    m-120,
    m-121,
    m-122,
    m-123,
    m-124,
    m-125,
    m-126,
    m-127,
    m-128
}

ENUM-129-0-FALSE ::= ENUMERATED {
    m-1,
    m-2,
    m-3,
    m-4,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33,
    m-34,
    m-35,
    m-36,
    m-37,
    m-38,
    m-39,
    m-40,
    m-41,
    m-42,
    m-43,
    m-44,
    m-45,
    m-46,
    m-47,
    m-48,
    m-49,
    m-50,
    m-51,
    m-52,
    m-53,
    m-54,
    m-55,
    m-56,
    m-57,
    m-58,
    m-59,
    m-60,
    m-61,
    m-62,
    m-63,
    m-64,
    m-65,
    m-66,
    m-67,
    m-68,
    m-69,
    m-70,
    m-71,
    m-72,
    m-73,
    m-74,
    m-75,
    m-76,
    m-77,
    m-78,
    m-79,
    m-80,
    m-81,
    m-82,
    m-83,
    m-84,
    m-85,
    m-86,
    m-87,
    m-88,
    m-89,
    m-90,
    m-91,
    m-92,
    m-93,
    m-94,
    m-95,
    m-96,
    m-97,
    m-98,
    m-99,
    m-100,
    m-101,
    m-102,
    m-103,
    m-104,
    m-105,
    m-106,
    m-107,
    m-108,
    m-109,
    m-110,
    m-111,
    m-112,
    m-113,
    m-114,
    m-115,
    m-116,
    m-117,
    m-118,
    m-119,
    m-120,
    m-121,
    m-122,
    m-123,
    m-124,
    m-125,
    m-126,
    m-127,
    m-128,
    m-129
}

ENUM-255-0-FALSE ::= ENUMERATED {
    m-1,
    m-2,
    m-3,
    m-4,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33,
    m-34,
    m-35,
    m-36,
    m-37,
    m-38,
    m-39,
    m-40,
    m-41,
    m-42,
    m-43,
    m-44,
    m-45,
    m-46,
    m-47,
    m-48,
    m-49,
    m-50,
    m-51,
    m-52,
    m-53,
    m-54,
    m-55,
    m-56,
    m-57,
    m-58,
    m-59,
    m-60,
    m-61,
    m-62,
    m-63,
    m-64,
    m-65,
    m-66,
    m-67,
    m-68,
    m-69,
    m-70,
    m-71,
    m-72,
    m-73,
    m-74,
    m-75,
    m-76,
    m-77,
    m-78,
    m-79,
    m-80,
    m-81,
    m-82,
    m-83,
    m-84,
    m-85,
    m-86,
    m-87,
    m-88,
    m-89,
    m-90,
    m-91,
    m-92,
    m-93,
    m-94,
    m-95,
    m-96,
    m-97,
    m-98,
    m-99,
    m-100,
    m-101,
    m-102,
    m-103,
    m-104,
    m-105,
    m-106,
    m-107,
    m-108,
    m-109,
    m-110,
    m-111,
    m-112,
    m-113,
    m-114,
    m-115,
    m-116,
    m-117,
    m-118,
    m-119,
    m-120,
    m-121,
    m-122,
    m-123,
    m-124,
    m-125,
    m-126,
    m-127,
    m-128,
    m-129,
    m-130,
    m-131,
    m-132,
    m-133,
    m-134,
    m-135,
    m-136,
    m-137,
    m-138,
    m-139,
    m-140,
    m-141,
    m-142,
    m-143,
    m-144,
    m-145,
    m-146,
    m-147,
    m-148,
    m-149,
    m-150,
    m-151,
    m-152,
    m-153,
    m-154,
    m-155,
    m-156,
    m-157,
    m-158,
    m-159,
    m-160,
    m-161,
    m-162,
    m-163,
    m-164,
    m-165,
    m-166,
    m-167,
    m-168,
    m-169,
    m-170,
    m-171,
    m-172,
    m-173,
    m-174,
    m-175,
    m-176,
    m-177,
    m-178,
    m-179,
    m-180,
    m-181,
    m-182,
    m-183,
    m-184,
    m-185,
    m-186,
    m-187,
    m-188,
    m-189,
    m-190,
    m-191,
    m-192,
    m-193,
    m-194,
    m-195,
    m-196,
    m-197,
    m-198,
    m-199,
    m-200,
    m-201,
    m-202,
    m-203,
    m-204,
    m-205,
    m-206,
    m-207,
    m-208,
    m-209,
    m-210,
    m-211,
    m-212,
    m-213,
    m-214,
    m-215,
    m-216,
    m-217,
    m-218,
    m-219,
    m-220,
    m-221,
    m-222,
    m-223,
    m-224,
    m-225,
    m-226,
    m-227,
    m-228,
    m-229,
    m-230,
    m-231,
    m-232,
    m-233,
    m-234,
    m-235,
    m-236,
    m-237,
    m-238,
    m-239,
    m-240,
    m-241,
    m-242,
    m-243,
    m-244,
    m-245,
    m-246,
    m-247,
    m-248,
    m-249,
    m-250,
    m-251,
    m-252,
    m-253,
    m-254,
    m-255
}

ENUM-256-0-FALSE ::= ENUMERATED {
    m-1,
    m-2,
    m-3,
    m-4,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33,
    m-34,
    m-35,
    m-36,
    m-37,
    m-38,
    m-39,
    m-40,
    m-41,
    m-42,
    m-43,
    m-44,
    m-45,
    m-46,
    m-47,
    m-48,
    m-49,
    m-50,
    m-51,
    m-52,
    m-53,
    m-54,
    m-55,
    m-56,
    m-57,
    m-58,
    m-59,
    m-60,
    m-61,
    m-62,
    m-63,
    m-64,
    m-65,
    m-66,
    m-67,
    m-68,
    m-69,
    m-70,
    m-71,
    m-72,
    m-73,
    m-74,
    m-75,
    m-76,
    m-77,
    m-78,
    m-79,
    m-80,
    m-81,
    m-82,
    m-83,
    m-84,
    m-85,
    m-86,
    m-87,
    m-88,
    m-89,
    m-90,
    m-91,
    m-92,
    m-93,
    m-94,
    m-95,
    m-96,
    m-97,
    m-98,
    m-99,
    m-100,
    m-101,
    m-102,
    m-103,
    m-104,
    m-105,
    m-106,
    m-107,
    m-108,
    m-109,
    m-110,
    m-111,
    m-112,
    m-113,
    m-114,
    m-115,
    m-116,
    m-117,
    m-118,
    m-119,
    m-120,
    m-121,
    m-122,
    m-123,
    m-124,
    m-125,
    m-126,
    m-127,
    m-128,
    m-129,
    m-130,
    m-131,
    m-132,
    m-133,
    m-134,
    m-135,
    m-136,
    m-137,
    m-138,
    m-139,
    m-140,
    m-141,
    m-142,
    m-143,
    m-144,
    m-145,
    m-146,
    m-147,
    m-148,
    m-149,
    m-150,
    m-151,
    m-152,
    m-153,
    m-154,
    m-155,
    m-156,
    m-157,
    m-158,
    m-159,
    m-160,
    m-161,
    m-162,
    m-163,
    m-164,
    m-165,
    m-166,
    m-167,
    m-168,
    m-169,
    m-170,
    m-171,
    m-172,
    m-173,
    m-174,
    m-175,
    m-176,
    m-177,
    m-178,
    m-179,
    m-180,
    m-181,
    m-182,
    m-183,
    m-184,
    m-185,
    m-186,
    m-187,
    m-188,
    m-189,
    m-190,
    m-191,
    m-192,
    m-193,
    m-194,
    m-195,
    m-196,
    m-197,
    m-198,
    m-199,
    m-200,
    m-201,
    m-202,
    m-203,
    m-204,
    m-205,
    m-206,
    m-207,
    m-208,
    m-209,
    m-210,
    m-211,
    m-212,
    m-213,
    m-214,
    m-215,
    m-216,
    m-217,
    m-218,
    m-219,
    m-220,
    m-221,
    m-222,
    m-223,
    m-224,
    m-225,
    m-226,
    m-227,
    m-228,
    m-229,
    m-230,
    m-231,
    m-232,
    m-233,
    m-234,
    m-235,
    m-236,
    m-237,
    m-238,
    m-239,
    m-240,
    m-241,
    m-242,
    m-243,
    m-244,
    m-245,
    m-246,
    m-247,
    m-248,
    m-249,
    m-250,
    m-251,
    m-252,
    m-253,
    m-254,
    m-255,
    m-256
}

ENUM-1-1-TRUE ::= ENUMERATED {
    m-1,
    ...,
    m-2
}

ENUM-2-2-TRUE ::= ENUMERATED {
    m-1,
    m-2,
    ...,
    m-3,
    m-4
}

ENUM-3-2-TRUE ::= ENUMERATED {
    m-1,
    m-2,
    m-3,
    ...,
    m-4,
    m-5
}

ENUM-4-256-TRUE ::= ENUMERATED {
    m-1,
    m-2,
    m-3,
    m-4,
    ...,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33,
    m-34,
    m-35,
    m-36,
    m-37,
    m-38,
    m-39,
    m-40,
    m-41,
    m-42,
    m-43,
    m-44,
    m-45,
    m-46,
    m-47,
    m-48,
    m-49,
    m-50,
    m-51,
    m-52,
    m-53,
    m-54,
    m-55,
    m-56,
    m-57,
    m-58,
    m-59,
    m-60,
    m-61,
    m-62,
    m-63,
    m-64,
    m-65,
    m-66,
    m-67,
    m-68,
    m-69,
    m-70,
    m-71,
    m-72,
    m-73,
    m-74,
    m-75,
    m-76,
    m-77,
    m-78,
    m-79,
    m-80,
    m-81,
    m-82,
    m-83,
    m-84,
    m-85,
    m-86,
    m-87,
    m-88,
    m-89,
    m-90,
    m-91,
    m-92,
    m-93,
    m-94,
    m-95,
    m-96,
    m-97,
    m-98,
    m-99,
    m-100,
    m-101,
    m-102,
    m-103,
    m-104,
    m-105,
    m-106,
    m-107,
    m-108,
    m-109,
    m-110,
    m-111,
    m-112,
    m-113,
    m-114,
    m-115,
    m-116,
    m-117,
    m-118,
    m-119,
    m-120,
    m-121,
    m-122,
    m-123,
    m-124,
    m-125,
    m-126,
    m-127,
    m-128,
    m-129,
    m-130,
    m-131,
    m-132,
    m-133,
    m-134,
    m-135,
    m-136,
    m-137,
    m-138,
    m-139,
    m-140,
    m-141,
    m-142,
    m-143,
    m-144,
    m-145,
    m-146,
    m-147,
    m-148,
    m-149,
    m-150,
    m-151,
    m-152,
    m-153,
    m-154,
    m-155,
    m-156,
    m-157,
    m-158,
    m-159,
    m-160,
    m-161,
    m-162,
    m-163,
    m-164,
    m-165,
    m-166,
    m-167,
    m-168,
    m-169,
    m-170,
    m-171,
    m-172,
    m-173,
    m-174,
    m-175,
    m-176,
    m-177,
    m-178,
    m-179,
    m-180,
    m-181,
    m-182,
    m-183,
    m-184,
    m-185,
    m-186,
    m-187,
    m-188,
    m-189,
    m-190,
    m-191,
    m-192,
    m-193,
    m-194,
    m-195,
    m-196,
    m-197,
    m-198,
    m-199,
    m-200,
    m-201,
    m-202,
    m-203,
    m-204,
    m-205,
    m-206,
    m-207,
    m-208,
    m-209,
    m-210,
    m-211,
    m-212,
    m-213,
    m-214,
    m-215,
    m-216,
    m-217,
    m-218,
    m-219,
    m-220,
    m-221,
    m-222,
    m-223,
    m-224,
    m-225,
    m-226,
    m-227,
    m-228,
    m-229,
    m-230,
    m-231,
    m-232,
    m-233,
    m-234,
    m-235,
    m-236,
    m-237,
    m-238,
    m-239,
    m-240,
    m-241,
    m-242,
    m-243,
    m-244,
    m-245,
    m-246,
    m-247,
    m-248,
    m-249,
    m-250,
    m-251,
    m-252,
    m-253,
    m-254,
    m-255,
    m-256,
    m-257,
    m-258,
    m-259,
    m-260
}

ENUM-7-2-TRUE ::= ENUMERATED {
    m-1,
    m-2,
    m-3,
    m-4,
    m-5,
    m-6,
    m-7,
    ...,
    m-8,
    m-9
}

ENUM-17-2-TRUE ::= ENUMERATED {
    m-1,
    m-2,
    m-3,
    m-4,
    m-5,
    m-6,
    m-7,
    m-8,
    m-9,
    m-10,
    m-11,
    m-12,
    m-13,
    m-14,
    m-15,
    m-16,
    m-17,
    ...,
    m-18,
    m-19
}

ENUM-128-4-TRUE ::= ENUMERATED {
    m-1,
    m-2,
    m-3,
    m-4,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33,
    m-34,
    m-35,
    m-36,
    m-37,
    m-38,
    m-39,
    m-40,
    m-41,
    m-42,
    m-43,
    m-44,
    m-45,
    m-46,
    m-47,
    m-48,
    m-49,
    m-50,
    m-51,
    m-52,
    m-53,
    m-54,
    m-55,
    m-56,
    m-57,
    m-58,
    m-59,
    m-60,
    m-61,
    m-62,
    m-63,
    m-64,
    m-65,
    m-66,
    m-67,
    m-68,
    m-69,
    m-70,
    m-71,
    m-72,
    m-73,
    m-74,
    m-75,
    m-76,
    m-77,
    m-78,
    m-79,
    m-80,
    m-81,
    m-82,
    m-83,
    m-84,
    m-85,
    m-86,
    m-87,
    m-88,
    m-89,
    m-90,
    m-91,
    m-92,
    m-93,
    m-94,
    m-95,
    m-96,
    m-97,
    m-98,
    m-99,
    m-100,
    m-101,
    m-102,
    m-103,
    m-104,
    m-105,
    m-106,
    m-107,
    m-108,
    m-109,
    m-110,
    m-111,
    m-112,
    m-113,
    m-114,
    m-115,
    m-116,
    m-117,
    m-118,
    m-119,
    m-120,
    m-121,
    m-122,
    m-123,
    m-124,
    m-125,
    m-126,
    m-127,
    m-128,
    ...,
    m-129,
    m-130,
    m-131,
    m-132
}

ENUM-129-2-TRUE ::= ENUMERATED {
    m-1,
    m-2,
    m-3,
    m-4,
    m-5,
    m-6,
    m-7,
    m-8,
    m-9,
    m-10,
    m-11,
    m-12,
    m-13,
    m-14,
    m-15,
    m-16,
    m-17,
    m-18,
    m-19,
    m-20,
    m-21,
    m-22,
    m-23,
    m-24,
    m-25,
    m-26,
    m-27,
    m-28,
    m-29,
    m-30,
    m-31,
    m-32,
    m-33,
    m-34,
    m-35,
    m-36,
    m-37,
    m-38,
    m-39,
    m-40,
    m-41,
    m-42,
    m-43,
    m-44,
    m-45,
    m-46,
    m-47,
    m-48,
    m-49,
    m-50,
    m-51,
    m-52,
    m-53,
    m-54,
    m-55,
    m-56,
    m-57,
    m-58,
    m-59,
    m-60,
    m-61,
    m-62,
    m-63,
    m-64,
    m-65,
    m-66,
    m-67,
    m-68,
    m-69,
    m-70,
    m-71,
    m-72,
    m-73,
    m-74,
    m-75,
    m-76,
    m-77,
    m-78,
    m-79,
    m-80,
    m-81,
    m-82,
    m-83,
    m-84,
    m-85,
    m-86,
    m-87,
    m-88,
    m-89,
    m-90,
    m-91,
    m-92,
    m-93,
    m-94,
    m-95,
    m-96,
    m-97,
    m-98,
    m-99,
    m-100,
    m-101,
    m-102,
    m-103,
    m-104,
    m-105,
    m-106,
    m-107,
    m-108,
    m-109,
    m-110,
    m-111,
    m-112,
    m-113,
    m-114,
    m-115,
    m-116,
    m-117,
    m-118,
    m-119,
    m-120,
    m-121,
    m-122,
    m-123,
    m-124,
    m-125,
    m-126,
    m-127,
    m-128,
    m-129,
    ...,
    m-130,
    m-131
}

END
