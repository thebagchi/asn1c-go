TestingPycrate DEFINITIONS AUTOMATIC TAGS ::= BEGIN

-- The types that only pycrate 0.8.1 answers. The generators give this module to pycrate and
-- not to OTP; testing.asn1 holds the types that both oracles compile. A row of one of these
-- types has no OTP answer. The kind of each type is in the vectors; a name is Strings-P
-- followed by a number.
--
-- Why OTP has no answer:
--   - A FROM with the extension marker crashes the OTP compiler (asn1ct_imm:string_num_bits).
--   - A FROM of one character does not compile for UPER in OTP.
--   - A FROM set with a character above U+007F: OTP reads the source as Latin-1 and so reads
--     the set as two characters.

Strings-P1  ::= IA5String (FROM("a"))
Strings-P2  ::= VisibleString (FROM("a"))
Strings-P3  ::= PrintableString (FROM("a"))
Strings-P4  ::= BMPString (FROM("a"))
Strings-P5  ::= UniversalString (FROM("a"))
Strings-P6  ::= VisibleString (FROM("a"))
Strings-P7  ::= IA5String (SIZE(3)) (FROM("a"))
Strings-P8  ::= IA5String (SIZE(1)) (FROM("a"))
Strings-P9  ::= IA5String (SIZE(5)) (FROM("a"))
Strings-P10 ::= IA5String (SIZE(9)) (FROM("a"))
Strings-P11 ::= IA5String (SIZE(1..4)) (FROM("a"))
Strings-P12 ::= IA5String (SIZE(0..3)) (FROM("a"))
Strings-P13 ::= IA5String (SIZE(2..20)) (FROM("a"))
Strings-P14 ::= IA5String (SIZE(3,...)) (FROM("a"))
Strings-P15 ::= IA5String (SIZE(1..4,...)) (FROM("a"))
Strings-P16 ::= VisibleString (SIZE(3)) (FROM("a"))
Strings-P17 ::= VisibleString (SIZE(1)) (FROM("a"))
Strings-P18 ::= VisibleString (SIZE(5)) (FROM("a"))
Strings-P19 ::= VisibleString (SIZE(9)) (FROM("a"))
Strings-P20 ::= VisibleString (SIZE(1..4)) (FROM("a"))
Strings-P21 ::= VisibleString (SIZE(0..3)) (FROM("a"))
Strings-P22 ::= VisibleString (SIZE(2..20)) (FROM("a"))
Strings-P23 ::= VisibleString (SIZE(3,...)) (FROM("a"))
Strings-P24 ::= VisibleString (SIZE(1..4,...)) (FROM("a"))
Strings-P25 ::= PrintableString (SIZE(3)) (FROM("a"))
Strings-P26 ::= PrintableString (SIZE(1)) (FROM("a"))
Strings-P27 ::= PrintableString (SIZE(5)) (FROM("a"))
Strings-P28 ::= PrintableString (SIZE(9)) (FROM("a"))
Strings-P29 ::= PrintableString (SIZE(1..4)) (FROM("a"))
Strings-P30 ::= PrintableString (SIZE(0..3)) (FROM("a"))
Strings-P31 ::= PrintableString (SIZE(2..20)) (FROM("a"))
Strings-P32 ::= PrintableString (SIZE(3,...)) (FROM("a"))
Strings-P33 ::= PrintableString (SIZE(1..4,...)) (FROM("a"))
Strings-P34 ::= BMPString (SIZE(3)) (FROM("a"))
Strings-P35 ::= BMPString (SIZE(1)) (FROM("a"))
Strings-P36 ::= BMPString (SIZE(5)) (FROM("a"))
Strings-P37 ::= BMPString (SIZE(9)) (FROM("a"))
Strings-P38 ::= BMPString (SIZE(1..4)) (FROM("a"))
Strings-P39 ::= BMPString (SIZE(0..3)) (FROM("a"))
Strings-P40 ::= BMPString (SIZE(2..20)) (FROM("a"))
Strings-P41 ::= BMPString (SIZE(3,...)) (FROM("a"))
Strings-P42 ::= BMPString (SIZE(1..4,...)) (FROM("a"))
Strings-P43 ::= UniversalString (SIZE(3)) (FROM("a"))
Strings-P44 ::= UniversalString (SIZE(1)) (FROM("a"))
Strings-P45 ::= UniversalString (SIZE(5)) (FROM("a"))
Strings-P46 ::= UniversalString (SIZE(9)) (FROM("a"))
Strings-P47 ::= UniversalString (SIZE(1..4)) (FROM("a"))
Strings-P48 ::= UniversalString (SIZE(0..3)) (FROM("a"))
Strings-P49 ::= UniversalString (SIZE(2..20)) (FROM("a"))
Strings-P50 ::= UniversalString (SIZE(3,...)) (FROM("a"))
Strings-P51 ::= UniversalString (SIZE(1..4,...)) (FROM("a"))
Strings-P52 ::= VisibleString (SIZE(3)) (FROM("a"))
Strings-P53 ::= VisibleString (SIZE(1)) (FROM("a"))
Strings-P54 ::= VisibleString (SIZE(5)) (FROM("a"))
Strings-P55 ::= VisibleString (SIZE(9)) (FROM("a"))
Strings-P56 ::= VisibleString (SIZE(1..4)) (FROM("a"))
Strings-P57 ::= VisibleString (SIZE(0..3)) (FROM("a"))
Strings-P58 ::= VisibleString (SIZE(2..20)) (FROM("a"))
Strings-P59 ::= VisibleString (SIZE(3,...)) (FROM("a"))
Strings-P60 ::= VisibleString (SIZE(1..4,...)) (FROM("a"))
Strings-P61 ::= NumericString (FROM(" "))
Strings-P62 ::= NumericString (SIZE(3)) (FROM(" "))
Strings-P63 ::= NumericString (SIZE(1)) (FROM(" "))
Strings-P64 ::= NumericString (SIZE(5)) (FROM(" "))
Strings-P65 ::= NumericString (SIZE(9)) (FROM(" "))
Strings-P66 ::= NumericString (SIZE(1..4)) (FROM(" "))
Strings-P67 ::= NumericString (SIZE(0..3)) (FROM(" "))
Strings-P68 ::= NumericString (SIZE(2..20)) (FROM(" "))
Strings-P69 ::= NumericString (SIZE(3,...)) (FROM(" "))
Strings-P70 ::= NumericString (SIZE(1..4,...)) (FROM(" "))
Strings-P71 ::= IA5String (FROM("a".."z",...))
Strings-P72 ::= IA5String (SIZE(1..4)) (FROM("ACGT",...))
Strings-P73 ::= IA5String (SIZE(3)) (FROM("a",...))
Strings-P74 ::= PrintableString (SIZE(1..4)) (FROM("0".."9",...))
Strings-P75 ::= NumericString (SIZE(4)) (FROM("0123456789",...))
Strings-P76 ::= VisibleString (FROM("a".."e",...))
Strings-P77 ::= BMPString (SIZE(0..5)) (FROM("abcdefghijklmnopqrstuvwxyz",...))
Strings-P78 ::= UniversalString (FROM("abcdefghijklmnopqrstuvwxyz",...))
Strings-P79 ::= IA5String (SIZE(1..4,...)) (FROM("a".."z",...))
Strings-P80 ::= IA5String (FROM("ab",...))
Strings-P81 ::= BMPString (FROM("ab",...))
Strings-P82 ::= PrintableString (FROM("ab",...))
Strings-P83 ::= BMPString (FROM("àéü中"))
Strings-P84 ::= BMPString (SIZE(3)) (FROM("àéü中"))
Strings-P85 ::= BMPString (FROM("àáâãä"))
Strings-P86 ::= BMPString (SIZE(3)) (FROM("àáâãä"))
Strings-P87 ::= UniversalString (FROM("😀😁😂"))
Strings-P88 ::= UniversalString (SIZE(3)) (FROM("😀😁😂"))
Strings-P89 ::= UniversalString (FROM("aé中😀􏿿"))
Strings-P90 ::= UniversalString (SIZE(3)) (FROM("aé中😀􏿿"))

END
